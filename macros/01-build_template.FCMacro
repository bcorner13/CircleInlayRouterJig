# -*- coding: utf-8 -*-
"""01-build_template — build Body `RecessTemplate` in CircleInlayRouterJig.FCStd.

plan.md rev 2, FEATURE TREE steps 1–9:
  DatumPlane_Base -> Sk_Plate/Pad_Plate -> Sk_Hole/Pocket_Hole (ThroughAll)
  -> Sk_Relief/Pocket_Relief (ReliefHeight, up from the bottom face)
  -> Sk_Standoff/Pocket_Standoff (optional ring foot; suppressed when StandoffHeight = 0)
  -> Sk_Notch/Pocket_Notch (V notch, ThroughAll) -> PolarPattern_Notches (x4)

Every sketch is fully constrained to the origin/axes; every dimension and feature length
is bound to <<Params>>#VarSet.<Name>. No literal dimensions.

Idempotent: if `RecessTemplate` already exists this does nothing, unless run with
REBUILD=True (run_macro args), which deletes the body and rebuilds it from scratch.
Opens this project's Params.FCStd if needed. Does NOT save the built body — the only
save is creating an empty CircleInlayRouterJig.FCStd when none exists (FreeCAD refuses
cross-document expressions from an unsaved document).
"""
import math
import os
import FreeCAD as App
import Part
import Sketcher

PROJECT_DIR = os.path.expanduser(
    "~/Documents/3dPrinting/Commercial License/CircleInlayRouterJig")
PARAMS_PATH = os.path.join(PROJECT_DIR, "Params.FCStd")
MODEL_PATH = os.path.join(PROJECT_DIR, "CircleInlayRouterJig.FCStd")
P = "<<Params>>#VarSet."

try:
    REBUILD
except NameError:
    REBUILD = False


def find_doc(path):
    for d in App.listDocuments().values():
        if d.FileName and os.path.abspath(d.FileName) == path:
            return d
    return None


params = find_doc(PARAMS_PATH) or App.openDocument(PARAMS_PATH)
vs = params.getObject("VarSet")


def v(name):
    return getattr(vs, name).Value


doc = find_doc(MODEL_PATH)
if doc is None:
    if os.path.exists(MODEL_PATH):
        doc = App.openDocument(MODEL_PATH)
    else:
        # Cross-document expressions refuse an unsaved owner ("Owner document not saved"),
        # so the new, empty model file must exist on disk before the first binding.
        doc = App.newDocument("CircleInlayRouterJig")
        doc.saveAs(MODEL_PATH)

old = doc.getObject("RecessTemplate")
if old is not None and not REBUILD:
    App.Console.PrintMessage("CIRJ-01: RecessTemplate exists; nothing to do (pass REBUILD=True to rebuild).\n")
else:
    if old is not None:
        old.removeObjectsFromDocument()
        doc.removeObject(old.Name)
        doc.recompute()

    body = doc.addObject("PartDesign::Body", "RecessTemplate")
    origin = {f.Role: f for f in body.Origin.OriginFeatures}

    # 1. Datum plane on the workpiece face (z = 0)
    dp = body.newObject("PartDesign::Plane", "DatumPlane_Base")
    dp.AttachmentSupport = [(origin["XY_Plane"], "")]
    dp.MapMode = "FlatFace"

    def new_sketch(name):
        sk = body.newObject("Sketcher::SketchObject", name)
        sk.AttachmentSupport = [(dp, "")]
        sk.MapMode = "FlatFace"
        return sk

    def bind(sk, idx, expr):
        sk.setExpression("Constraints[%d]" % idx, expr)

    # 2–3. Plate: square TemplateSide with PlateCornerRadius rounded corners, symmetric about
    #   the origin, padded TemplateThick. Corners are rounded IN THE SKETCH (tangent arcs with a
    #   bound radius) rather than with a PartDesign Fillet, which would select edges by index.
    S, R = v("TemplateSide"), v("PlateCornerRadius")
    h = S / 2
    sk = new_sketch("Sk_Plate")
    # lines 0..3: bottom, right, top, left (counter-clockwise); arcs 4..7 at BR, TR, TL, BL corners
    sk.addGeometry(Part.LineSegment(App.Vector(-h + R, -h, 0), App.Vector(h - R, -h, 0)))
    sk.addGeometry(Part.LineSegment(App.Vector(h, -h + R, 0), App.Vector(h, h - R, 0)))
    sk.addGeometry(Part.LineSegment(App.Vector(h - R, h, 0), App.Vector(-h + R, h, 0)))
    sk.addGeometry(Part.LineSegment(App.Vector(-h, h - R, 0), App.Vector(-h, -h + R, 0)))
    centers = [(h - R, -h + R), (h - R, h - R), (-h + R, h - R), (-h + R, -h + R)]
    starts = [-math.pi / 2, 0, math.pi / 2, math.pi]
    for (cx, cy), a0 in zip(centers, starts):
        sk.addGeometry(Part.ArcOfCircle(Part.Circle(App.Vector(cx, cy, 0), App.Vector(0, 0, 1), R), a0, a0 + math.pi / 2))
    # arc i (4+i) runs CCW from the end of line i to the start of line i+1 — endpoint tangency
    for i in range(4):
        sk.addConstraint(Sketcher.Constraint("Tangent", i, 2, 4 + i, 1))
        sk.addConstraint(Sketcher.Constraint("Tangent", 4 + i, 2, (i + 1) % 4, 1))
    sk.addConstraint(Sketcher.Constraint("Horizontal", 0))
    sk.addConstraint(Sketcher.Constraint("Horizontal", 2))
    sk.addConstraint(Sketcher.Constraint("Vertical", 1))
    sk.addConstraint(Sketcher.Constraint("Vertical", 3))
    for i in (5, 6, 7):
        sk.addConstraint(Sketcher.Constraint("Equal", 4, i))
    c = sk.addConstraint(Sketcher.Constraint("Radius", 4, R))
    bind(sk, c, P + "PlateCornerRadius")
    # centre the plate: opposite arc centres symmetric about the origin
    sk.addConstraint(Sketcher.Constraint("Symmetric", 7, 3, 5, 3, -1, 1))
    c = sk.addConstraint(Sketcher.Constraint("DistanceX", 3, 1, 1, 1, S))    # left line -> right line
    bind(sk, c, P + "TemplateSide")
    c = sk.addConstraint(Sketcher.Constraint("DistanceY", 0, 1, 2, 1, S))    # bottom line -> top line
    bind(sk, c, P + "TemplateSide")

    pad = body.newObject("PartDesign::Pad", "Pad_Plate")
    pad.Profile = sk
    pad.Length = v("TemplateThick")
    pad.setExpression("Length", P + "TemplateThick")

    def circle_sketch(name, dia_param):
        sk = new_sketch(name)
        sk.addGeometry(Part.Circle(App.Vector(0, 0, 0), App.Vector(0, 0, 1), v(dia_param) / 2))
        sk.addConstraint(Sketcher.Constraint("Coincident", 0, 3, -1, 1))
        c = sk.addConstraint(Sketcher.Constraint("Diameter", 0, v(dia_param)))
        bind(sk, c, P + dia_param)
        return sk

    # 4–5. Bearing-wall hole, through all (cut upward from the z = 0 sketch)
    po = body.newObject("PartDesign::Pocket", "Pocket_Hole")
    po.Profile = circle_sketch("Sk_Hole", "TemplateHoleModelD")
    po.Type = "ThroughAll"
    po.Reversed = True

    # 6–7. Underside relief: ReliefDiameter x ReliefHeight, cut up from the bottom face
    pr = body.newObject("PartDesign::Pocket", "Pocket_Relief")
    pr.Profile = circle_sketch("Sk_Relief", "ReliefDiameter")
    pr.Type = "Length"
    pr.Length = v("ReliefHeight")
    pr.setExpression("Length", P + "ReliefHeight")
    pr.Reversed = True

    # 7b. Optional standoff ring foot (StandoffHeight; suppressed when 0).
    #   Removes StandoffHeight of material from the UNDERSIDE everywhere outside a ring of
    #   diameter FootRingDiameter around the relief. The ring stays on the field around the
    #   inlay; a low lip can pass under the raised margin. The bearing band is measured from
    #   the wood, so it does not move. Profile = two concentric circles: FootRingDiameter and an
    #   outer circle of 2 x TemplateSide, which overshoots every plate corner.
    sk = new_sketch("Sk_Standoff")
    sk.addGeometry(Part.Circle(App.Vector(0, 0, 0), App.Vector(0, 0, 1), S))
    sk.addGeometry(Part.Circle(App.Vector(0, 0, 0), App.Vector(0, 0, 1), v("FootRingDiameter") / 2))
    sk.addConstraint(Sketcher.Constraint("Coincident", 0, 3, -1, 1))
    sk.addConstraint(Sketcher.Constraint("Coincident", 1, 3, -1, 1))
    c = sk.addConstraint(Sketcher.Constraint("Diameter", 0, 2 * S))
    bind(sk, c, "2 * " + P + "TemplateSide")
    c = sk.addConstraint(Sketcher.Constraint("Diameter", 1, v("FootRingDiameter")))
    bind(sk, c, P + "FootRingDiameter")
    ps = body.newObject("PartDesign::Pocket", "Pocket_Standoff")
    ps.Profile = sk
    ps.Type = "Length"
    ps.Length = v("StandoffHeight")
    ps.setExpression("Length", P + "StandoffHeight")
    ps.Reversed = True
    ps.setExpression("Suppressed", P + "StandoffHeight == 0mm")

    # 8–9. V alignment notch on the +X edge, then x4 polar pattern.
    #   Apex A on the X axis, AlignNotchDepth inside the edge; the outer corners B/C sit the same
    #   distance OUTSIDE the edge at ±AlignNotchWidth, so the V is exactly AlignNotchWidth wide
    #   where it crosses the plate edge (similar triangles) and cuts the edge cleanly.
    W, D = v("AlignNotchWidth"), v("AlignNotchDepth")
    sk = new_sketch("Sk_Notch")
    A = App.Vector(S / 2 - D, 0, 0)
    B = App.Vector(S / 2 + D, W, 0)
    C = App.Vector(S / 2 + D, -W, 0)
    sk.addGeometry(Part.LineSegment(A, B))     # 0: A->B
    sk.addGeometry(Part.LineSegment(B, C))     # 1: B->C
    sk.addGeometry(Part.LineSegment(C, A))     # 2: C->A
    sk.addConstraint(Sketcher.Constraint("Coincident", 0, 2, 1, 1))
    sk.addConstraint(Sketcher.Constraint("Coincident", 1, 2, 2, 1))
    sk.addConstraint(Sketcher.Constraint("Coincident", 2, 2, 0, 1))
    # B, C symmetric about the H axis (this also makes B-C vertical — no extra Vertical)
    sk.addConstraint(Sketcher.Constraint("Symmetric", 0, 2, 1, 2, -1))
    sk.addConstraint(Sketcher.Constraint("PointOnObject", 0, 1, -1))       # apex on the X axis
    c = sk.addConstraint(Sketcher.Constraint("DistanceX", -1, 1, 0, 1, S / 2 - D))
    bind(sk, c, P + "TemplateSide / 2 - " + P + "AlignNotchDepth")
    c = sk.addConstraint(Sketcher.Constraint("DistanceX", 0, 1, 0, 2, 2 * D))
    bind(sk, c, "2 * " + P + "AlignNotchDepth")
    c = sk.addConstraint(Sketcher.Constraint("DistanceY", 1, 2, 1, 1, 2 * W))
    bind(sk, c, "2 * " + P + "AlignNotchWidth")

    pn = body.newObject("PartDesign::Pocket", "Pocket_Notch")
    pn.Profile = sk
    pn.Type = "ThroughAll"
    pn.Reversed = True

    pp = body.newObject("PartDesign::PolarPattern", "PolarPattern_Notches")
    pp.Originals = [pn]
    pp.Axis = (origin["Z_Axis"], [""])
    pp.Occurrences = 4      # one notch per square edge (topology, not a dimension)
    body.Tip = pp

    doc.recompute()
    App.Console.PrintMessage("CIRJ-01: RecessTemplate built. Not saved.\n")
