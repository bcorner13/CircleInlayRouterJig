# -*- coding: utf-8 -*-
"""00-bootstrap_params — create/refresh Params.FCStd for CircleInlayRouterJig.

Idempotent:
  - Opens Params.FCStd if it exists, otherwise creates the Params document.
  - Adds missing VarSet properties with their default value; EXISTING values are
    never overwritten (tuned values survive a re-run).
  - (Re)applies the derived-value expressions every run, so the formulas live
    in exactly one place.
  - Does NOT save. Review in FreeCAD, then save Params.FCStd yourself.

Run only after plan.md is approved. Defaults marked TBD are placeholders.
Matches plan.md rev 2 (top-bearing pattern bit).
"""
import os
import FreeCAD as App

PROJECT_DIR = os.path.expanduser(
    "~/Documents/3dPrinting/Commercial License/CircleInlayRouterJig")
PARAMS_PATH = os.path.join(PROJECT_DIR, "Params.FCStd")

# (name, type, group, default, doc)
PARAMS = [
    ("InlayDiameter",         "App::PropertyLength", "Inlay",     150.0,  "Nominal laser-cut disc diameter (size knob)"),
    ("LaserKerf",             "App::PropertyLength", "Inlay",     0.0,    "Diameter lost by the disc to laser kerf; measured < .0007 in (0.018 mm), negligible"),
    ("RecessDepth",           "App::PropertyLength", "Inlay",     3.2,    "Routed depth = thickest disc (3.1-3.2); engraved discs sit flush to 0.1 below; drives plate height"),
    ("CutterDiameter",        "App::PropertyLength", "Tooling",   9.525,  "Measured cutter diameter, 3/8in pattern bit [TBD measure]"),
    ("CutterLength",          "App::PropertyLength", "Tooling",   9.525,  "Measured cutting length [TBD measure]"),
    ("BearingOD",             "App::PropertyLength", "Tooling",   9.525,  "Measured bearing OD [TBD measure]"),
    ("BearingStackHeight",    "App::PropertyLength", "Tooling",   5.2,    "Both bearings together; estimated from listing drawing [TBD measure]"),
    ("RouterBaseDiameter",    "App::PropertyLength", "Tooling",   146.05, "Milwaukee M18 FUEL 2723-20 sub-base, 5-3/4in"),
    ("InlayFitClearance",     "App::PropertyLength", "Clearance", 0.05,   "Per-side glue gap, disc <-> recess wall"),
    ("TemplateHolePrintComp", "App::PropertyLength", "Clearance", 0.15,   "Per-side FDM undersize comp for the printed hole (per material)"),
    ("ReliefClearance",       "App::PropertyLength", "Clearance", 1.0,    "Per-side radial gap, cutter <-> underside relief wall"),
    ("ReliefGap",             "App::PropertyLength", "Template",  1.0,    "Vertical gap, cutter top <-> relief ceiling"),
    ("CollarGap",             "App::PropertyLength", "Template",  1.0,    "Vertical gap, plate top <-> bit lock-collar bottom"),
    ("BaseSupportOverlap",    "App::PropertyLength", "Template",  2.0,    "Plate beyond the router base's outer edge, bearing on the wall"),
    ("AlignNotchWidth",       "App::PropertyLength", "Template",  16.0,   "V alignment notch: mouth width at the plate edge (16 x 8 deep = 90 deg V)"),
    ("AlignNotchDepth",       "App::PropertyLength", "Template",  8.0,    "V alignment notch: depth from the plate edge to the apex"),
    ("PlateCornerRadius",     "App::PropertyLength", "Template",  10.0,   "Fillet radius of the plate's four outer corners (in Sk_Plate)"),
    ("StandoffHeight",        "App::PropertyLength", "Standoff",  0.0,    "Optional ring-foot standoff: underside outside the foot ring is raised this much so a low lip can pass under the margin. 0 = off (feature suppressed)"),
    ("FootRingWidth",         "App::PropertyLength", "Standoff",  15.0,   "Radial width of the ring foot around the relief (rests on the field around the inlay)"),
    ("LabelSize",             "App::PropertyLength", "Label",     10.0,   "Engraved size-label text height"),
    ("LabelDepth",            "App::PropertyLength", "Label",     0.6,    "Engraved size-label depth into the top face"),
    ("LabelInset",            "App::PropertyLength", "Label",     12.0,   "Label offset from the plate's corner edges (outside the router-base sweep)"),
    # Derived — value is set by expression below
    ("RecessDiameter",        "App::PropertyLength", "Derived",   0.0,    "Routed recess diameter (derived)"),
    ("TemplateHoleDiameter",  "App::PropertyLength", "Derived",   0.0,    "Functional hole diameter = bearing wall (derived)"),
    ("TemplateHoleModelD",    "App::PropertyLength", "Derived",   0.0,    "Hole as modeled incl. print comp (derived)"),
    ("ReliefDiameter",        "App::PropertyLength", "Derived",   0.0,    "Underside relief diameter (derived)"),
    ("ReliefHeight",          "App::PropertyLength", "Derived",   0.0,    "Underside relief height (derived)"),
    ("TemplateThick",         "App::PropertyLength", "Derived",   0.0,    "Plate thickness (derived)"),
    ("BearingBand",           "App::PropertyLength", "Derived",   0.0,    "Wall height the bearing rides; validation only (derived)"),
    ("FootRingDiameter",      "App::PropertyLength", "Derived",   0.0,    "Outer diameter of the standoff ring foot (derived)"),
    ("TemplateMargin",        "App::PropertyLength", "Derived",   0.0,    "Plate material outside the hole, each side (derived)"),
    ("TemplateSide",          "App::PropertyLength", "Derived",   0.0,    "Square plate side (derived)"),
]

DERIVED = {
    "RecessDiameter":       "InlayDiameter - LaserKerf + 2 * InlayFitClearance",
    "TemplateHoleDiameter": "RecessDiameter + BearingOD - CutterDiameter",
    "TemplateHoleModelD":   "TemplateHoleDiameter + 2 * TemplateHolePrintComp",
    "ReliefDiameter":       "TemplateHoleDiameter + 2 * ReliefClearance",
    "ReliefHeight":         "CutterLength - RecessDepth + ReliefGap",
    "TemplateThick":        "CutterLength - RecessDepth + BearingStackHeight - CollarGap",
    "BearingBand":          "TemplateThick - ReliefHeight",
    "FootRingDiameter":     "ReliefDiameter + 2 * FootRingWidth",
    "TemplateMargin":       "RouterBaseDiameter / 2 - BearingOD / 2 + BaseSupportOverlap",
    "TemplateSide":         "TemplateHoleDiameter + 2 * TemplateMargin",
}

MIN_BEARING_BAND = 2.5   # mm — plan.md Validation 4
BED_SIZE = 350.0         # mm — Creality K2 Plus


def get_params_doc():
    # Match by FILE PATH only. Other projects also have a doc named/labelled "Params";
    # touching theirs would corrupt them, and two "Params" labels make <<Params>> ambiguous.
    for d in App.listDocuments().values():
        if d.FileName and os.path.abspath(d.FileName) == PARAMS_PATH:
            return d
    for d in App.listDocuments().values():
        if d.Name == "Params" or d.Label == "Params":
            raise RuntimeError(
                "CIRJ-00: another project's Params is open (%s). Close it first — "
                "<<Params>> expressions resolve by label." % (d.FileName or d.Name))
    if os.path.exists(PARAMS_PATH):
        return App.openDocument(PARAMS_PATH)
    return App.newDocument("Params")


doc = get_params_doc()
vs = doc.getObject("VarSet") or doc.addObject("App::VarSet", "VarSet")

added, kept = [], []
for name, ptype, group, default, docstr in PARAMS:
    if name in vs.PropertiesList:
        kept.append(name)
        continue
    vs.addProperty(ptype, name, group, docstr)
    setattr(vs, name, default)
    added.append(name)

for name, expr in DERIVED.items():
    vs.setExpression(name, expr)

doc.recompute()

App.Console.PrintMessage(
    "CIRJ-00: added %d, kept %d existing. Recess=%.3f Hole=%.3f HoleModel=%.3f Relief=%.3fx%.3f "
    "Thick=%.3f Band=%.3f Side=%.3f\n" % (
        len(added), len(kept), vs.RecessDiameter.Value, vs.TemplateHoleDiameter.Value,
        vs.TemplateHoleModelD.Value, vs.ReliefDiameter.Value, vs.ReliefHeight.Value,
        vs.TemplateThick.Value, vs.BearingBand.Value, vs.TemplateSide.Value))
if vs.BearingBand.Value < MIN_BEARING_BAND:
    App.Console.PrintError("CIRJ-00: BearingBand %.2f < %.1f mm — bearing has too little wall to ride\n"
                           % (vs.BearingBand.Value, MIN_BEARING_BAND))
if vs.TemplateSide.Value > BED_SIZE:
    App.Console.PrintError("CIRJ-00: TemplateSide %.1f > %.0f mm bed — this size needs the segmented-plate backlog item (plan.md BACKLOG)\n"
                           % (vs.TemplateSide.Value, BED_SIZE))
App.Console.PrintMessage("CIRJ-00: not saved. Save Params.FCStd to %s after review.\n" % PROJECT_DIR)
